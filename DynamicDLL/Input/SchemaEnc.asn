--<ASN1.HugeInteger World-Schema.Rocket.range>--
World-Schema DEFINITIONS AUTOMATIC TAGS ::= 
BEGIN
	Company ::= SEQUENCE {
		id INTEGER,
		name IA5String
	}

	Vendor ::= SEQUENCE {
		id INTEGER,
		domestic BOOLEAN,
		company Company
	}

  	Rocket ::= SEQUENCE       
  	{
     		range     INTEGER, -- huge (see a special directive above)
     		name      UTF8String (SIZE(1..16)),
     		message   UTF8String DEFAULT "Hello World" , 
     		fuel      ENUMERATED {solid, liquid, gas},
		vendor    Vendor
  	}                                                     
END
